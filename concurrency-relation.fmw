FME workspace concurrency-relation.fmw

Parameters:
- PERP_YEAR_NBR = 2016   # What's the perp year of incoming data
- RIMS_TEST = C:\Users\jjiang\AppData\Roaming\ESRI\Desktop10.5\ArcCatalog\RIMS_TEST.sde   # Connection File

Readers:
- XLSXR_1: XLSXR from W:\GIS Projects\Primary secondary relations for BTRS-Lavanya Sugumar-110117\Source dataset\Nlf_id_prioritization.xlsx
- GEODATABASE_SDE_1: GEODATABASE_SDE

Writers:
- SQLITE3_1: SQLITE3 to W:\GIS Projects\Primary secondary relations for BTRS-Lavanya Sugumar-110117\Result\primary-secondary-v4.sqlite

Junction_15
    -> Junction_16
Junction_16
    -> Sorter

Bookmark: Create temporary GDB location
Creator
    GEOMTYPE = Geometry Object
    NUM = 1
    CREATED -> AttributeCreator_4
Note: Set the input feature type
AttributeCreator_4
    ATTR_TABLE = SET_TO fme_feature_type = jump_starter
    -> TempPathnameCreator
Note: Create temp location
TempPathnameCreator
    PATHNAME_ATTR = _pathname
    -> SchemaSetter
Note: Create schema from first feature
SchemaSetter
    SORT = None
    -> FeatureWriter [Output]

Bookmark: Write concurrency calculation output table to a temp fgdb
Note: Write to temp gdb
FeatureWriter
    DATASET_ATTR = _dataset
    TOTAL_FEATURES_WRITTEN_ATTR = _total_features_written
    GEODATABASE_FILE_X_ORIGIN = 0
    GEODATABASE_FILE_DUMP_FAILED_FEATURES = no
    GEODATABASE_FILE_SIMPLIFY_NETWORK_FEATURES = no
    GEODATABASE_FILE_XY_SCALE = 0
    GEODATABASE_FILE_Z_SCALE = 0
    GEODATABASE_FILE_TRANSACTION = 0
    GEODATABASE_FILE_HAS_Z_VALUES = auto_detect
    GEODATABASE_FILE_IGNORE_FAILED_FEATURE_ENTRY = no
    GEODATABASE_FILE_ANNOTATION_UNITS = unknown_units
    GEODATABASE_FILE_Z_ORIGIN = 0
    GEODATABASE_FILE_OVERWRITE_GEODB = NO
    GEODATABASE_FILE_TRANSACTION_INTERVAL = 1000
    GEODATABASE_FILE_COMPRESS_AT_END = no
    GEODATABASE_FILE_DESTINATION_DATASETTYPE_VALIDATION = Yes
    GEODATABASE_FILE_DEFAULT_Z_VALUE = 0
    GEODATABASE_FILE_HAS_MEASURES = no
    GEODATABASE_FILE_TRANSACTION_TYPE = TRANSACTIONS
    GEODATABASE_FILE_MAX_NUMBER_FAILED_FEATURES = -1
    GEODATABASE_FILE_VALIDATE_FEATURES = no
    FEATURE_TYPE_LIST_ATTR = _feature_type
    GEODATABASE_FILE_WRITER_MODE = INSERT
    FORMAT = GEODATABASE_FILE
    GEODATABASE_FILE_GRID_1 = 0
    GEODATABASE_FILE_COORDINATE_SYSTEM_GRANULARITY = FEATURE_TYPE
    GEODATABASE_FILE_Y_ORIGIN = 0
    GEODATABASE_FILE_REQUESTED_GEODATABASE_VERSION = CURRENT
    GEODATABASE_FILE_SIMPLIFY_GEOM = No
    DATASET = @Value(_pathname)\temp.gdb
    SUMMARY -> StringReplacer
Note: Fix path slashes
StringReplacer
    REPLACE_TEXT = /
    FIND_TEXT = \
    CASE = NO
    SRC_ATTRS = _dataset
    REGEXP = NO
    NO_MATCH = _FME_NO_OP_
    -> PythonCaller
Note: Write Concurrencies_Output to the temp gdb
PythonCaller
    PYTHONSOURCE:
      import fme
      import fmeobjects
      import arcpy

      def processFeature(feature):
          #
          TargetDataset = feature.getAttribute('_dataset')
          print TargetDataset

          SourceDataset = fme.macroValues['RIMS_TEST']
          print SourceDataset
          arcpy.env.workspace = SourceDataset

          print arcpy.CheckOutExtension("Highways")

          # Set local variables
          network = "RH.LRSN_COUNTY_NETWORK"
          output_table = TargetDataset + "/Concurrencies_Output"
          print "Variables Set"

          arcpy.CalculateRouteConcurrencies_locref(network, output_table, "", "")
          print "Concurrencies Calculation Finish"

          print arcpy.CheckInExtension("Highways")
    PYTHONSYMBOL = processFeature
    -> FeatureReader [INITIATOR]

Bookmark: Read concurrency calculation output table back to workflow
Note: Read back output feature class
FeatureReader
    GEODATABASE_FILE_FEATURE_READ_MODE = Features
    GEODATABASE_FILE_RESOLVE_DOMAINS = no
    GEODATABASE_FILE_IGNORE_NETWORK_INFO = yes
    ATTR_CONFLICT_RES = Use Result
    INTERACT = <No Spatial Filter>
    GEODATABASE_FILE_ALIAS_MODE = NONE
    GEODATABASE_FILE_CACHE_MULTIPATCH_TEXTURES = yes
    GEODATABASE_FILE_MERGE_FEAT_LINKED_ANNOS = no
    GEODATABASE_FILE_QUERY_FEATURE_TYPES_FOR_MERGE_FILTERS = Yes
    GEODATABASE_FILE_IGNORE_RELATIONSHIP_INFO = yes
    GEODATABASE_FILE_SPLIT_MULTI_PART_ANNOS = no
    GEODATABASE_FILE_TRANSLATE_SPATIAL_DATA_ONLY = no
    ATTR_ACCUM_MODE = Merge Initiator and Result
    GEODATABASE_FILE_RESOLVE_SUBTYPE_NAMES = yes
    GEODATABASE_FILE_SPLIT_COMPLEX_EDGES = no
    FEATURETYPES = Concurrencies_Output
    OUTPUT_FEATURES_DISPLAY = Schema and Data Features
    FORMAT = GEODATABASE_FILE
    GEODATABASE_FILE_USE_SEARCH_ENVELOPE = NO
    COMBINE_GEOM = Use Result
    GEODATABASE_FILE_SPLIT_COMPLEX_ANNOS = no
    DATASET = @Value(_dataset)
    GEODATABASE_FILE_CHECK_SIMPLE_GEOM = no
    <OTHER> -> AttributeRemover
Note: Remove temporary attributes
AttributeRemover
    LIST_ATTRS = _feature_type{}
    REMOVE_ATTRS = _total_features_written,_Group_Attrs,_dataset
    -> AttributeExposer
AttributeExposer
    ATTR_LIST = RouteId,SectionId,FromMeasure,ToMeasure
    -> AttributeRounder_2
AttributeRounder_2
    PLACES = 3
    ROUND_TYPE = Nearest
    SRC_ATTRS = FromMeasure ToMeasure
    -> Tester_2

Bookmark: Filter out problem data
Note: Measure from and measure to need to have values
Tester_2
    TEST_CLAUSE:
      TEST @Value(FromMeasure) ATTRIBUTE_HAS_VALUE ""
      TEST @Value(ToMeasure) ATTRIBUTE_HAS_VALUE ""
    BOOL_OP = AND
    TEST_MODE = Automatic
    TEST_DESCRIPTION = ""
    PASSED -> DuplicateFilter
    FAILED -> Junction_17
DuplicateFilter
    INPUT_ORDERED_CHOICE = No
    KEYATTR = FromMeasure SectionId ToMeasure RouteId
    UNIQUE -> Junction_21
    UNIQUE -> Junction_19
Note: Calculation: Nlf_id_prioritization [XLSXR]
Junction_21
    -> Junction_22
Junction_19
    -> Junction_20
Junction_17
    -> Junction_18

Bookmark: Add NLFID scores
Junction_22
    -> Route_Type [REQUESTOR]
Junction_2
    -> AttributeKeeper
AttributeKeeper
    KEEP_ATTRS = Route Type,Route_type_priority
    -> Route_Type [SUPPLIER]
Route_Type: FeatureMerger
    ATTR_CONFLICT_RES = Use Requestor
    SUPPLIERS_FIRST = No
    PROCESS_DUPS = Yes
    CONNECT_Z_MODE = First Wins
    MERGE_TYPE = Attributes Only
    GEOM_TYPE = Build Polygons
    IGNORE_NULLS = No
    JOIN_KEYS = @Substring(@Value(RouteId),4,2) @Value(Route Type) AUTO
    ATTR_ACCUM_MODE = Merge Supplier
    REJECT_NULL_MISSING_KEYS = No
    MERGED -> ROUTE_NUM [REQUESTOR]
Junction_8
    -> AttributeKeeper_4
AttributeKeeper_4
    KEEP_ATTRS = State_Suffix,State_Suffix_Priority
    -> STATE_SUFFIX [SUPPLIER]
Junction_12
    -> AttributeKeeper_5
AttributeKeeper_5
    KEEP_ATTRS = Jurisdiction,Jur_priority
    -> JURISDICTION [SUPPLIER]
Junction_10
    -> AttributeKeeper_6
AttributeKeeper_6
    KEEP_ATTRS = Cardinality_priority,Cardinality
    -> CARDINALITY [SUPPLIER]
Junction_6
    -> AttributeKeeper_3
AttributeKeeper_3
    KEEP_ATTRS = Local_Suffix_Priority,Local_Suffix
    -> Local_Suffix [SUPPLIER]
Junction_4
    -> AttributeKeeper_2
AttributeKeeper_2
    KEEP_ATTRS = ROUTE_NUM,Route_Nbr_priority
    -> ROUTE_NUM [SUPPLIER]
ROUTE_NUM: FeatureMerger
    ATTR_CONFLICT_RES = Use Requestor
    SUPPLIERS_FIRST = No
    PROCESS_DUPS = Yes
    CONNECT_Z_MODE = First Wins
    MERGE_TYPE = Attributes Only
    GEOM_TYPE = Build Polygons
    IGNORE_NULLS = No
    JOIN_KEYS = @Substring(@Value(RouteId),6,5) @Value(ROUTE_NUM) AUTO
    ATTR_ACCUM_MODE = Merge Supplier
    REJECT_NULL_MISSING_KEYS = No
    MERGED -> Local_Suffix [REQUESTOR]
Local_Suffix: FeatureMerger
    ATTR_CONFLICT_RES = Use Requestor
    SUPPLIERS_FIRST = No
    PROCESS_DUPS = Yes
    CONNECT_Z_MODE = First Wins
    MERGE_TYPE = Attributes Only
    GEOM_TYPE = Build Polygons
    IGNORE_NULLS = No
    JOIN_KEYS = @Substring(@Value(RouteId),11,1) @Value(Local_Suffix) AUTO
    ATTR_ACCUM_MODE = Merge Supplier
    REJECT_NULL_MISSING_KEYS = No
    MERGED -> STATE_SUFFIX [REQUESTOR]
STATE_SUFFIX: FeatureMerger
    ATTR_CONFLICT_RES = Use Requestor
    SUPPLIERS_FIRST = No
    PROCESS_DUPS = Yes
    CONNECT_Z_MODE = First Wins
    MERGE_TYPE = Attributes Only
    GEOM_TYPE = Build Polygons
    IGNORE_NULLS = No
    JOIN_KEYS = @Substring(@Value(RouteId),12,1) @Value(State_Suffix) AUTO
    ATTR_ACCUM_MODE = Merge Supplier
    REJECT_NULL_MISSING_KEYS = No
    MERGED -> JURISDICTION [REQUESTOR]
JURISDICTION: FeatureMerger
    ATTR_CONFLICT_RES = Use Requestor
    SUPPLIERS_FIRST = No
    PROCESS_DUPS = Yes
    CONNECT_Z_MODE = First Wins
    MERGE_TYPE = Attributes Only
    GEOM_TYPE = Build Polygons
    IGNORE_NULLS = No
    JOIN_KEYS = @Substring(@Value(RouteId),0,1) @Value(Jurisdiction) AUTO
    ATTR_ACCUM_MODE = Merge Supplier
    REJECT_NULL_MISSING_KEYS = No
    MERGED -> CARDINALITY [REQUESTOR]
CARDINALITY: FeatureMerger
    ATTR_CONFLICT_RES = Use Requestor
    SUPPLIERS_FIRST = No
    PROCESS_DUPS = Yes
    CONNECT_Z_MODE = First Wins
    MERGE_TYPE = Attributes Only
    GEOM_TYPE = Build Polygons
    IGNORE_NULLS = No
    JOIN_KEYS = @Substring(@Value(RouteId),13,1) @Value(Cardinality) AUTO
    ATTR_ACCUM_MODE = Merge Supplier
    REJECT_NULL_MISSING_KEYS = No
    MERGED -> COUNTY [REQUESTOR]
Junction_14
    -> AttributeKeeper_7
AttributeKeeper_7
    KEEP_ATTRS = County_priority,County
    -> COUNTY [SUPPLIER]
COUNTY: FeatureMerger
    ATTR_CONFLICT_RES = Use Requestor
    SUPPLIERS_FIRST = No
    PROCESS_DUPS = Yes
    CONNECT_Z_MODE = First Wins
    MERGE_TYPE = Attributes Only
    GEOM_TYPE = Build Polygons
    IGNORE_NULLS = No
    JOIN_KEYS = @Substring(@Value(RouteId),1,3) @Value(County) AUTO
    ATTR_ACCUM_MODE = Merge Supplier
    REJECT_NULL_MISSING_KEYS = No
    MERGED -> Junction_15

Bookmark: Result
Junction_20
    -> DateTimeStamper_4
DateTimeStamper_4
    STAMP_TYPE = date
    TIMEZONE = local
    DATETIME_ATTR = _timestamp
    -> Concurrency_Output (writer SQLITE3_1)
Concurrency_Output (writer SQLITE3_1) [off]
    attributes: RouteId text, SectionId text, FromMeasure text, ToMeasure text
Junction_18
    -> DateTimeStamper_3
DateTimeStamper_3
    STAMP_TYPE = date
    TIMEZONE = local
    DATETIME_ATTR = _timestamp
    -> LRS_secondaries0000 (writer SQLITE3_1)
LRS_secondaries0000 (writer SQLITE3_1) [off]
    attributes: RouteId text, SectionId text, FromMeasure text, ToMeasure text
UUIDGenerator
    UUID_ATTR = _uuid
    -> DateTimeStamper
DateTimeStamper
    STAMP_TYPE = date
    TIMEZONE = local
    DATETIME_ATTR = _timestamp
    -> LRS_secondaries00 (writer SQLITE3_1)
LRS_secondaries00 (writer SQLITE3_1)
    attributes: OVERLAP_SEGMENT_ID integer, PERP_YEAR_NBR integer, SectionId text, NLF_ID text, CTL_BEGIN_NBR float, CTL_END_NBR float, SEC_NLF_ID text, SEC_CTL_BEGIN_NBR float, SEC_CTL_END_NBR float, INCONSISTENT_IND text
UUIDGenerator_2
    UUID_ATTR = _uuid
    -> DateTimeStamper_2
DateTimeStamper_2
    STAMP_TYPE = date
    TIMEZONE = local
    DATETIME_ATTR = _timestamp
    -> LRS_secondaries02 (writer SQLITE3_1)
LRS_secondaries02 (writer SQLITE3_1)
    attributes: ADJOINING_SEGMENT_ID integer, PERP_YEAR_NBR integer, SectionId text, NLF_ID text, CTL_BEGIN_NBR float, CTL_END_NBR float, ADJ_NLF_ID text, ADJ_CTL_BEGIN_NBR float, ADJ_CTL_END_NBR float, INCONSISTENT_IND text

Bookmark: NLFID prioritization table
Calculation (reader XLSXR_1)
    attributes: Route Type char(3), Route_type_priority number(4,0), ROUTE_NUM number(6,0), Route_Nbr_priority number(9,0), Local_Suffix char(2), Local_Suffix_Priority number(4,0), State_Suffix char(2), State_Suffix_Priority number(4,0), Jurisdiction char(2), Jur_priority number(3,0), Cardinality char(2), Cardinality_priority number(3,0), County char(4), County_priority number(4,0)
    -> Junction
    -> Junction_3
    -> Junction_5
    -> Junction_7
    -> Junction_9
    -> Junction_11
    -> Junction_13
Junction
    -> Junction_2
Junction_7
    -> Junction_8
Junction_11
    -> Junction_12
Junction_9
    -> Junction_10
Junction_5
    -> Junction_6
Junction_3
    -> Junction_4
Junction_13
    -> Junction_14

Bookmark: NLFID ranking
Note: Sort records according to order of priority
Sorter
    SORT_PARM = SectionId ALPHA ASCENDING Route_type_priority NUMERIC ASCENDING Route_Nbr_priority NUMERIC ASCENDING Local_Suffix_Priority NUMERIC ASCENDING State_Suffix_Priority NUMERIC ASCENDING Jur_priority NUMERIC ASCENDING Cardinality_priority NUMERIC ASCENDING County_priority NUMERIC ASCENDING
    SORTED -> ListBuilder
    SORTED -> PythonCaller_2
Note: Overlap
Note: Build list based on sectionId and county
ListBuilder
    LIST_NAME = _list
    GROUP_BY = SectionId County
    GROUPS_ORDERED = No
    LIST_ATTRS_TO_INCLUDE = FromMeasure RouteId ToMeasure
    -> AttributeRemover_2
AttributeRemover_2
    REMOVE_ATTRS = County
    -> AttributeCreator_2
Note: Put out the route with highest ranking / as primary route
AttributeCreator_2
    ATTR_TABLE:
      SET_TO NLF_ID = @Value(_list{0}.RouteId)
      SET_TO CTL_BEGIN_NBR = @Value(_list{0}.FromMeasure)
      SET_TO CTL_END_NBR = @Value(_list{0}.ToMeasure)
    -> ListExploder
Note: List all secondary routes
ListExploder
    LIST_ATTR = _list{}
    ATTR_CONFLICT_RES = Use List Attribute Values
    ATTR_ACCUM_MODE = Merge List Attributes
    INDEX_ATTR = _element_index
    ELEMENTS -> Tester
Tester
    TEST_CLAUSE = TEST @Value(_element_index) != 0
    BOOL_OP = OR
    TEST_MODE = Automatic
    TEST_DESCRIPTION = ""
    PASSED -> AttributeManager
Note: Filter down to routes with highest ranking of each county
Note: Spilt
PythonCaller_2
    PYTHONSOURCE:
      import fme
      import fmeobjects

      # Template Class Interface:
      # When using this class, make sure its name is set as the value of
      # the 'Class or Function to Process Features' transformer parameter
      class FeatureProcessor(object):
          def __init__(self):
              self.featureList = []
              self.sectionList = []

          def input(self,feature):
              if feature.getAttribute('SectionId') not in self.sectionList:
                  self.sectionList.append(feature.getAttribute('SectionId'))
                  self.countyList = []
                  if feature.getAttribute('County') not in self.countyList:
                      self.countyList.append(feature.getAttribute('County'))
                      self.featureList.append(feature)
              else:
                  if feature.getAttribute('County') not in self.countyList:
                      self.countyList.append(feature.getAttribute('County'))
                      self.featureList.append(feature)


          def close(self):
              for feature in self.featureList:
                  self.pyoutput(feature)
    PYTHONSYMBOL = FeatureProcessor
    -> ListBuilder_2
Note: Build list based on sectionId
ListBuilder_2
    LIST_NAME = _list
    GROUP_BY = SectionId
    GROUPS_ORDERED = No
    LIST_ATTRS_TO_INCLUDE = FromMeasure RouteId ToMeasure
    -> AttributeCreator_5
Note: Put out the route with highest ranking / as primary route
AttributeCreator_5
    ATTR_TABLE:
      SET_TO NLF_ID = @Value(_list{0}.RouteId)
      SET_TO CTL_BEGIN_NBR = @Value(_list{0}.FromMeasure)
      SET_TO CTL_END_NBR = @Value(_list{0}.ToMeasure)
    -> ListExploder_2
Note: List all secondary routes
ListExploder_2
    LIST_ATTR = _list{}
    ATTR_CONFLICT_RES = Use List Attribute Values
    ATTR_ACCUM_MODE = Merge List Attributes
    INDEX_ATTR = _element_index
    ELEMENTS -> Tester_4
Tester_4
    TEST_CLAUSE = TEST @Value(_element_index) != 0
    BOOL_OP = OR
    TEST_MODE = Automatic
    TEST_DESCRIPTION = ""
    PASSED -> AttributeManager_2

Bookmark: Length consistency check
AttributeManager
    ATTR_TABLE:
      RENAME_SET_VALUE RouteId > SECONDARY_NLF_ID
      RENAME_SET_VALUE FromMeasure > SEC_CTL_BEGIN_NBR
      RENAME_SET_VALUE ToMeasure > SEC_CTL_END_NBR
      REMOVE _element_index
      SET_TO PriLength = @Evaluate(@abs(@Value(CTL_BEGIN_NBR)-@Value(CTL_END_NBR)))
      SET_TO SecLength = @Evaluate(@abs(@Value(SEC_CTL_END_NBR)-@Value(SEC_CTL_BEGIN_NBR)))
    -> AttributeRounder_3
AttributeRounder_3
    PLACES = 3
    ROUND_TYPE = Nearest
    SRC_ATTRS = PriLength SecLength
    -> Tester_7
Tester_7
    TEST_CLAUSE = TEST @Value(PriLength) = @Value(SecLength)
    BOOL_OP = OR
    TEST_MODE = Automatic
    TEST_DESCRIPTION = ""
    PASSED -> Tester_9
    FAILED -> Tester_9
AttributeManager_2
    ATTR_TABLE:
      RENAME_SET_VALUE RouteId > SECONDARY_NLF_ID
      RENAME_SET_VALUE FromMeasure > SEC_CTL_BEGIN_NBR
      RENAME_SET_VALUE ToMeasure > SEC_CTL_END_NBR
      REMOVE _element_index
      SET_TO PriLength = @Evaluate(@abs(@Value(CTL_BEGIN_NBR)-@Value(CTL_END_NBR)))
      SET_TO SecLength = @Evaluate(@abs(@Value(SEC_CTL_END_NBR)-@Value(SEC_CTL_BEGIN_NBR)))
    -> AttributeRounder_4
AttributeRounder_4
    PLACES = 3
    ROUND_TYPE = Nearest
    SRC_ATTRS = PriLength SecLength
    -> Tester_8
Tester_8
    TEST_CLAUSE = TEST @Value(PriLength) = @Value(SecLength)
    BOOL_OP = OR
    TEST_MODE = Automatic
    TEST_DESCRIPTION = ""
    PASSED -> Tester_5
    FAILED -> Tester_5

Bookmark: Attribute swapping when sec from measure larger than to measure
Tester_9
    TEST_CLAUSE = TEST @Value(SEC_CTL_BEGIN_NBR) > @Value(SEC_CTL_END_NBR)
    BOOL_OP = OR
    TEST_MODE = Automatic
    TEST_DESCRIPTION = ""
    PASSED -> AttributeSwapper
    FAILED -> AttributeCreator
AttributeSwapper
    COMP_MODE = Automatic
    CONDITION = UNCONDITIONAL
    ATTR_A = SEC_CTL_BEGIN_NBR
    ATTR_B = SEC_CTL_END_NBR
    -> AttributeSwapper_2
AttributeSwapper_2
    COMP_MODE = Automatic
    CONDITION = UNCONDITIONAL
    ATTR_A = CTL_BEGIN_NBR
    ATTR_B = CTL_END_NBR
    -> AttributeCreator
AttributeCreator
    ATTR_TABLE:
      SET_TO TYPE = Overlap
      SET_TO PERP_YEAR_NBR = $(PERP_YEAR_NBR)
    -> UUIDGenerator
Tester_5
    TEST_CLAUSE = TEST @Value(SEC_CTL_BEGIN_NBR) > @Value(SEC_CTL_END_NBR)
    BOOL_OP = OR
    TEST_MODE = Automatic
    TEST_DESCRIPTION = ""
    PASSED -> AttributeSwapper_5
    FAILED -> AttributeCreator_3
AttributeSwapper_5
    COMP_MODE = Automatic
    CONDITION = UNCONDITIONAL
    ATTR_A = SEC_CTL_BEGIN_NBR
    ATTR_B = SEC_CTL_END_NBR
    -> AttributeSwapper_6
AttributeSwapper_6
    COMP_MODE = Automatic
    CONDITION = UNCONDITIONAL
    ATTR_A = CTL_BEGIN_NBR
    ATTR_B = CTL_END_NBR
    -> AttributeCreator_3
AttributeCreator_3
    ATTR_TABLE:
      SET_TO TYPE = Split
      SET_TO PERP_YEAR_NBR = $(PERP_YEAR_NBR)
    -> UUIDGenerator_2

FME custom transformer SchemaSetter
This transformer adds both exposed and unexposed attributes to a feature-based schema, with appropriate data types. 
For example: if a feature has the following attributes:
    Attribute(boolean) : `mybool' has value `Yes'
    Attribute(32 bit integer): `myint' has value `12'
    Attribute(64 bit real) : `myreal' has value `12.965'
the following list attributes will be added:
    Attribute(string) : `attribute{0}.fme_data_type' has value `fme_boolean' 
    Attribute(encoded: utf-8): `attribute{0}.name' has value `mybool' 
    Attribute(string) : `attribute{1}.fme_data_type' has value `fme_int32' 
    Attribute(encoded: utf-8): `attribute{1}.name' has value `myint' 
    Attribute(string) : `attribute{2}.fme_data_type' has value `fme_real64' 
    Attribute(encoded: utf-8): `attribute{2}.name' has value `myreal' 
The transformer also gives users the option to exclude certain attributes based on name or prefix, and automatically excludes all "fme_" attributes.
Input Ports
Features containing attributes for which a schema definition is required. 
    Output Ports
All features are output. Attributes which have been selected to be excluded are removed from the feature. The list containing the schema of the feature is added to each feature. 
    Parameters
    Attributes to Exclude
A selected set of attributes that will be excluded from the generated schema list and removed from the feature.
    Prefixes to Exclude
A comma-delimited list of prefixes for attributes that are to be excluded from the generated schema list and removed from the feature. Regular expressions are not supported. For example: "date" will exclude any attributes that start with the letters "date" e.g. date_created, dateupdated
    Sort Attributes
(Ascending, Descending, None) Set this parameter to alphabetically sort output attributes.
    Usage Notes
The feature based schema can be passed to any writer that it set to Dynamic Mode and used with the "Schema from First Feature" setting.
Please see 
        https://knowledge.safe.com/articles/1051/dynamic-workflow-tutorial-destination-schema-is-de-2.html 
    for more information on feature-based schema using list attributes.

Parameters:
- AttributesToExclude =   # " " Attributes to exclude
- PrefixesToExclude =   # Prefixes to exclude
- SORT = None   # Sort Attributes

Input (input)
    -> ParameterFetcher
Note: Retrieve Parameters
ParameterFetcher
    ATTR_LIST = _AttributesToExclude {$(AttributesToExclude)} _PrefixesToExclude {$(PrefixesToExclude)} _sort {$(SORT)}
    -> PythonCaller
Note: See Comment in Code
PythonCaller
    PYTHONSOURCE:
      from __future__ import absolute_import, division, print_function, unicode_literals

      import fmeobjects
      import six

      #Checks if a list entry starts with a certain string
      def StringLikeList(list,string):
              test=False
              for element in list:
                  if string.startswith(element):
                      test=True
              return test

       # Checks if a list contains an element equal to a certain string
      def StringInList(list,string):
              test=False
              for element in list:
                  if string==element:
                      test=True
              return test

      # Template Class Interface:
      class FeatureProcessor(object):

          typesMapping = {
              fmeobjects.FME_ATTR_UNDEFINED : None,
              fmeobjects.FME_ATTR_BOOLEAN : "fme_boolean",
              fmeobjects.FME_ATTR_INT8 : "fme_int8",
              fmeobjects.FME_ATTR_UINT8 : "fme_uint8",
              fmeobjects.FME_ATTR_INT16 : "fme_int16",
              fmeobjects.FME_ATTR_UINT16 : "fme_uint16",
              fmeobjects.FME_ATTR_INT32 : "fme_int32",
              fmeobjects.FME_ATTR_UINT32 : "fme_uint32",
              fmeobjects.FME_ATTR_REAL32 : "fme_real32",
              fmeobjects.FME_ATTR_REAL64 : "fme_real64",
              fmeobjects.FME_ATTR_REAL80 : "fme_real80",
              fmeobjects.FME_ATTR_STRING : "fme_char(255)",
              fmeobjects.FME_ATTR_ENCODED_STRING : "fme_varchar(255)",
              fmeobjects.FME_ATTR_INT64 : "fme_int64",
              fmeobjects.FME_ATTR_UINT64 : "fme_uint64"
           }

          def __init__(self):
              pass
          def input(self,feature):
              #create a new feature
              nfeature=fmeobjects.FMEFeature()
              #get list of all attributes on feature
              attlist=feature.getAllAttributeNames()
              #loop through all attributes and add to schema if they fail exclusion criteria
              i=0
              ExcludedAttributes=str(feature.getAttribute('_AttributesToExclude')).split(",")
              ExcludedPrefixes=str(feature.getAttribute('_PrefixesToExclude')).split(",")

              # remove all fme_ attributes from list - don't want to include these in dynamic schema
              ExcludedPrefixes = ['fme_'] if ExcludedPrefixes == [''] else ExcludedPrefixes + ["fme_"]

              # sorting attributes
              if feature.getAttribute('_sort') == 'Ascending' or feature.getAttribute('_sort') == 'Descending':
                  attlist.sort()
                  if feature.getAttribute('_sort') == 'Descending':
                      attlist.reverse()

              for att in attlist:
                  if not StringInList(ExcludedAttributes,att) and not StringLikeList(ExcludedPrefixes,att) and not att=='_AttributesToExclude' and not att=='_PrefixesToExclude' and not att=='_sort':
                     type=feature.getAttributeType(att)
                     #Check datatype and set in schema
                     type = self.typesMapping[type]

                     if type is None:
                         feature.removeAttribute(att)
                     else:
                         #add schema attributes to feature
                         nfeature.setAttribute("attribute{"+str(i)+"}.fme_data_type",type)
                         nfeature.setAttribute("attribute{"+str(i)+"}.name",six.text_type(att))
                         nfeature.setAttribute(att,feature.getAttribute(att))
                         i+=1;
              #copy original geometry to new feature
              nfeature.setGeometry(feature.getGeometry())
              nfeature.setCoordSys(feature.getCoordSys())
              nfeature.setFeatureType(feature.getFeatureType())
              nfeature.setAttribute("fme_geometry{0}",feature.getAttribute("fme_type"))
              nfeature.setAttribute("fme_feature_type",feature.getAttribute("fme_feature_type"))
              self.pyoutput(nfeature)
          def close(self):
              pass
    PYTHONSYMBOL = FeatureProcessor
    -> Output (output)
Output (output)

FME custom transformer AttributeSwapper
Swaps the values and internal storage data types of specified two attributes (A and B).
By default, swapping will be performed unconditionally, but optionally you can choose one of these conditional swapping modes. 
"A < B" [A_LT_B]: Swap the values only when A is less than B. 
"A > B" [A_GT_B]: Swap the values only when A is greater than B. 
Leading/trailing spaces and leading zeros will be ignored when the values are being compared as NUMERIC; will NOT be ignored when the values are being compared as STRING.
The <null> and <missing> will also be swapped, but those will be treated as the empty string when comparing values in conditional swapping mode. 
A new attribute called "_swapped" will be added to the output features; its value indicates whether the two attribute values have been swapped. 
_swapped = 1: the values have been swapped. 
_swapped = 0: the values have not been swapped.
Only when you set "A < B" or "A > B" to the "Swapping Condition" parameter and set "Numeric" to the "Comparison Mode" parameter, the input feature will be output via the <Rejected> port if a specified attribute stores a non-numeric value.
Parameters 
Attribute A / Attribute B : 
Select two attributes whose values should be swapped. 
Swap Condition :
Select one of these swapping condition. 
"Unconditional" [UNCONDITIONAL]: Swap the values unconditionally (default). 
"A < B" [A_LT_B]: Swap the values only when A is less than B. 
"A > B" [A_GT_B]: Swap the values only when A is greater than B. 
Comparison Mode :
Select one of these comparison mode for conditional swapping. This parameter setting will be just ignored when you have set "Unconditional" to the "Swap Condition" parameter.
"Automatic": The transformer will compare the values as numeric values if possible, and as strings otherwise. 
"String": The transformer will always compare the values as strings.
"Numeric": The transformer will always compare the values as numeric values. If a value is not numeric, the input feature will be output via the <Rejected> port (only when you have set "A < B" or "A > B" to the "Swap Condition" parameter).

Parameters:
- ATTR_A =   # " " Attribute A
- ATTR_B =   # " " Attribute B
- CONDITION = UNCONDITIONAL   # < B,A_LT_B%A > B,A_GT_B Swap Condition
- COMP_MODE = Automatic   # Comparison Mode

Input (input)
    -> ParameterFetcher
ParameterFetcher
    ATTR_LIST = __attributeswapper.attr_a {$(ATTR_A)} __attributeswapper.attr_b {$(ATTR_B)} __attributeswapper.condition {$(CONDITION)} __attributeswapper.comp_mode {$(COMP_MODE)}
    -> TclCaller
TclCaller
    SRC:
      proc swapAttributes {} {
          set result -1
          set attr_a [FME_GetAttribute "__attributeswapper.attr_a"]
          set attr_b [FME_GetAttribute "__attributeswapper.attr_b"]
          set condition [FME_GetAttribute "__attributeswapper.condition"]
          if {[string equal $condition "UNCONDITIONAL"]} {
              set result 1
          } else {
              proc trimLeftZero {s} {
                  set v [string trimleft [set t [string trim $s]] {0}]
                  if {[string length $v]==0 && 0<[string length $t]} {
                      return 0
                  } else {
                      return $v
                  }
              }
              set a [FME_GetAttribute $attr_a]
              set b [FME_GetAttribute $attr_b]
              set mode [FME_GetAttribute "__attributeswapper.comp_mode"]
              switch $mode {
                  "String" {
                      switch $condition {
                          "A_LT_B" {set result [expr [string compare $a $b] < 0]}
                          "A_GT_B" {set result [expr [string compare $a $b] > 0]}
                      }
                  }
                  default {
                      set x [trimLeftZero $a]
                      set y [trimLeftZero $b]
                      if {[string is double -strict $x] && [string is double -strict $y]} {
                          switch $condition {
                              "A_LT_B" {set result [expr $x < $y]}
                              "A_GT_B" {set result [expr $x > $y]}
                          }
                      } elseif {[string equal $mode "Automatic"]} {
                          switch $condition {
                              "A_LT_B" {set result [expr [string compare $a $b] < 0]}
                              "A_GT_B" {set result [expr [string compare $a $b] > 0]}
                          }
                      }
                  }
              }
          }
          if {$result == 1} {
              FME_RenameAttribute "__attributeswapper.tmp" $attr_a
              FME_RenameAttribute $attr_a $attr_b
              FME_RenameAttribute $attr_b "__attributeswapper.tmp"
          }
          return $result
      }
    TCLPROG = swapAttributes
    VAL_ATTR = _swapped
    -> Tester
Tester
    TEST_CLAUSE = TEST 0 <= @Value(_swapped)
    BOOL_OP = OR
    TEST_MODE = Automatic
    TEST_DESCRIPTION = ""
    PASSED -> Output (output)
    FAILED -> <Rejected> (output)
Output (output)
<Rejected> (output)
